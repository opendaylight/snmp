/*
 * This module has been generated by smidump 0.4.8:
 *
 *      smidump -f yang IANAifType-MIB
 *
 * Do not edit. Edit the source file instead!
 */

module IANAifType-MIB {

  /*** NAMESPACE / PREFIX DEFINITION ***/

  namespace "urn:ietf:params:xml:ns:yang:smiv2:IANAifType-MIB";
  prefix "ianaiftype-mib";

  /*** LINKAGE (IMPORTS / INCLUDES) ***/


  /*** META INFORMATION ***/

  organization      
   "IANA";

  contact           
   "        Internet Assigned Numbers Authority
    
    Postal: ICANN
            4676 Admiralty Way, Suite 330
            Marina del Rey, CA 90292
    
    Tel:    +1 310 823 9358
    E-Mail: iana&iana.org";

  description       
   "This MIB module defines the IANAifType Textual
    Convention, and thus the enumerated values of
    the ifType object defined in MIB-II's ifTable.";

  revision "2010-02-11" {
    description     
     "Registration of new IANAifType 254.";
  }
  revision "2010-02-08" {
    description     
     "Registration of new IANAifTypes 252 and 253.";
  }
  revision "2009-05-06" {
    description     
     "Registration of new IANAifType 251.";
  }
  revision "2009-02-06" {
    description     
     "Registration of new IANAtunnelType 15.";
  }
  revision "2008-10-09" {
    description     
     "Registration of new IANAifType 250.";
  }
  revision "2008-08-12" {
    description     
     "Registration of new IANAifType 249.";
  }
  revision "2008-07-22" {
    description     
     "Registration of new IANAifTypes 247 and 248.";
  }
  revision "2008-06-24" {
    description     
     "Registration of new IANAifType 246.";
  }
  revision "2008-05-29" {
    description     
     "Registration of new IANAifType 245.";
  }
  revision "2007-09-13" {
    description     
     "Registration of new IANAifTypes 243 and 244.";
  }
  revision "2007-05-29" {
    description     
     "Changed the description for IANAifType 228.";
  }
  revision "2007-03-08" {
    description     
     "Registration of new IANAifType 242.";
  }
  revision "2007-01-23" {
    description     
     "Registration of new IANAifTypes 239, 240, and 241.";
  }
  revision "2006-10-17" {
    description     
     "Deprecated/Obsoleted IANAifType 230.  Registration of 
      IANAifType 238.";
  }
  revision "2006-09-25" {
    description     
     "Changed the description for IANA ifType 
      184 and added new IANA ifType 237.";
  }
  revision "2006-08-17" {
    description     
     "Changed the descriptions for IANAifTypes
      20 and 21.";
  }
  revision "2006-08-11" {
    description     
     "Changed the descriptions for IANAifTypes
      7, 11, 62, 69, and 117.";
  }
  revision "2006-07-25" {
    description     
     "Registration of new IANA ifType 236.";
  }
  revision "2006-06-14" {
    description     
     "Registration of new IANA ifType 235.";
  }
  revision "2006-03-31" {
    description     
     "Registration of new IANA ifType 234.";
  }
  revision "2006-03-30" {
    description     
     "Registration of new IANA ifType 233.";
  }
  revision "2005-12-22" {
    description     
     "Registration of new IANA ifTypes 231 and 232.";
  }
  revision "2005-10-10" {
    description     
     "Registration of new IANA ifType 230.";
  }
  revision "2005-09-09" {
    description     
     "Registration of new IANA ifType 229.";
  }
  revision "2005-05-27" {
    description     
     "Registration of new IANA ifType 228.";
  }
  revision "2005-03-03" {
    description     
     "Added the IANAtunnelType TC and deprecated
      IANAifType sixToFour (215) per RFC4087.";
  }
  revision "2004-11-22" {
    description     
     "Registration of new IANA ifType 227 per RFC4631.";
  }
  revision "2004-06-17" {
    description     
     "Registration of new IANA ifType 226.";
  }
  revision "2004-05-12" {
    description     
     "Added description for IANAifType 6, and 
      changed the descriptions for IANAifTypes
      180, 181, and 182.";
  }
  revision "2004-05-07" {
    description     
     "Registration of new IANAifType 225.";
  }
  revision "2003-08-25" {
    description     
     "Deprecated IANAifTypes 7 and 11. Obsoleted
      IANAifTypes 62, 69, and 117.  ethernetCsmacd (6)
      should be used instead of these values";
  }
  revision "2003-08-18" {
    description     
     "Registration of new IANAifType
      224.";
  }
  revision "2003-08-07" {
    description     
     "Registration of new IANAifTypes
      222 and 223.";
  }
  revision "2003-03-18" {
    description     
     "Registration of new IANAifType
      221.";
  }
  revision "2003-01-13" {
    description     
     "Registration of new IANAifType
      220.";
  }
  revision "2002-10-17" {
    description     
     "Registration of new IANAifType
      219.";
  }
  revision "2002-07-16" {
    description     
     "Registration of new IANAifTypes
      217 and 218.";
  }
  revision "2002-07-10" {
    description     
     "Registration of new IANAifTypes
      215 and 216.";
  }
  revision "2002-06-19" {
    description     
     "Registration of new IANAifType
      214.";
  }
  revision "2002-01-04" {
    description     
     "Registration of new IANAifTypes
      211, 212 and 213.";
  }
  revision "2001-12-20" {
    description     
     "Registration of new IANAifTypes
      209 and 210.";
  }
  revision "2001-11-15" {
    description     
     "Registration of new IANAifTypes
      207 and 208.";
  }
  revision "2001-11-06" {
    description     
     "Registration of new IANAifType
      206.";
  }
  revision "2001-11-02" {
    description     
     "Registration of new IANAifType
      205.";
  }
  revision "2001-10-16" {
    description     
     "Registration of new IANAifTypes
      199, 200, 201, 202, 203, and 204.";
  }
  revision "2001-09-19" {
    description     
     "Registration of new IANAifType
      198.";
  }
  revision "2001-05-11" {
    description     
     "Registration of new IANAifType
      197.";
  }
  revision "2001-01-12" {
    description     
     "Registration of new IANAifTypes
      195 and 196.";
  }
  revision "2000-12-19" {
    description     
     "Registration of new IANAifTypes
      193 and 194.";
  }
  revision "2000-12-07" {
    description     
     "Registration of new IANAifTypes
      191 and 192.";
  }
  revision "2000-12-04" {
    description     
     "Registration of new IANAifType
      190.";
  }
  revision "2000-10-17" {
    description     
     "Registration of new IANAifTypes
      188 and 189.";
  }
  revision "2000-10-02" {
    description     
     "Registration of new IANAifType 187.";
  }
  revision "2000-09-01" {
    description     
     "Registration of new IANAifTypes
      184, 185, and 186.";
  }
  revision "2000-08-24" {
    description     
     "Registration of new IANAifType 183.";
  }
  revision "2000-08-23" {
    description     
     "Registration of new IANAifTypes
      174-182.";
  }
  revision "2000-08-22" {
    description     
     "Registration of new IANAifTypes 170,
      171, 172 and 173.";
  }
  revision "2000-04-25" {
    description     
     "Registration of new IANAifTypes 168 and 169.";
  }
  revision "2000-03-06" {
    description     
     "Fixed a missing semi-colon in the IMPORT.
      Also cleaned up the REVISION log a bit.
      It is not complete, but from now on it will
      be maintained and kept up to date with each
      change to this MIB module.";
  }
  revision "1999-10-08" {
    description     
     "Include new name assignments up to cnr(85).
      This is the first version available via the WWW
      at: ftp://ftp.isi.edu/mib/ianaiftype.mib";
  }
  revision "1994-01-31" {
    description     
     "Initial version of this MIB as published in
      RFC 1573.";
  }

  /*** TYPE DEFINITIONS ***/

  typedef IANAifType {
    type enumeration {
      enum other                         { value 1; }
      enum regular1822                   { value 2; }
      enum hdh1822                       { value 3; }
      enum ddnX25                        { value 4; }
      enum rfc877x25                     { value 5; }
      enum ethernetCsmacd                { value 6; }
      enum iso88023Csmacd                { value 7; }
      enum iso88024TokenBus              { value 8; }
      enum iso88025TokenRing             { value 9; }
      enum iso88026Man                   { value 10; }
      enum starLan                       { value 11; }
      enum proteon10Mbit                 { value 12; }
      enum proteon80Mbit                 { value 13; }
      enum hyperchannel                  { value 14; }
      enum fddi                          { value 15; }
      enum lapb                          { value 16; }
      enum sdlc                          { value 17; }
      enum ds1                           { value 18; }
      enum e1                            { value 19; }
      enum basicISDN                     { value 20; }
      enum primaryISDN                   { value 21; }
      enum propPointToPointSerial        { value 22; }
      enum ppp                           { value 23; }
      enum softwareLoopback              { value 24; }
      enum eon                           { value 25; }
      enum ethernet3Mbit                 { value 26; }
      enum nsip                          { value 27; }
      enum slip                          { value 28; }
      enum ultra                         { value 29; }
      enum ds3                           { value 30; }
      enum sip                           { value 31; }
      enum frameRelay                    { value 32; }
      enum rs232                         { value 33; }
      enum para                          { value 34; }
      enum arcnet                        { value 35; }
      enum arcnetPlus                    { value 36; }
      enum atm                           { value 37; }
      enum miox25                        { value 38; }
      enum sonet                         { value 39; }
      enum x25ple                        { value 40; }
      enum iso88022llc                   { value 41; }
      enum localTalk                     { value 42; }
      enum smdsDxi                       { value 43; }
      enum frameRelayService             { value 44; }
      enum v35                           { value 45; }
      enum hssi                          { value 46; }
      enum hippi                         { value 47; }
      enum modem                         { value 48; }
      enum aal5                          { value 49; }
      enum sonetPath                     { value 50; }
      enum sonetVT                       { value 51; }
      enum smdsIcip                      { value 52; }
      enum propVirtual                   { value 53; }
      enum propMultiplexor               { value 54; }
      enum ieee80212                     { value 55; }
      enum fibreChannel                  { value 56; }
      enum hippiInterface                { value 57; }
      enum frameRelayInterconnect        { value 58; }
      enum aflane8023                    { value 59; }
      enum aflane8025                    { value 60; }
      enum cctEmul                       { value 61; }
      enum fastEther                     { value 62; }
      enum isdn                          { value 63; }
      enum v11                           { value 64; }
      enum v36                           { value 65; }
      enum g703at64k                     { value 66; }
      enum g703at2mb                     { value 67; }
      enum qllc                          { value 68; }
      enum fastEtherFX                   { value 69; }
      enum channel                       { value 70; }
      enum ieee80211                     { value 71; }
      enum ibm370parChan                 { value 72; }
      enum escon                         { value 73; }
      enum dlsw                          { value 74; }
      enum isdns                         { value 75; }
      enum isdnu                         { value 76; }
      enum lapd                          { value 77; }
      enum ipSwitch                      { value 78; }
      enum rsrb                          { value 79; }
      enum atmLogical                    { value 80; }
      enum ds0                           { value 81; }
      enum ds0Bundle                     { value 82; }
      enum bsc                           { value 83; }
      enum async                         { value 84; }
      enum cnr                           { value 85; }
      enum iso88025Dtr                   { value 86; }
      enum eplrs                         { value 87; }
      enum arap                          { value 88; }
      enum propCnls                      { value 89; }
      enum hostPad                       { value 90; }
      enum termPad                       { value 91; }
      enum frameRelayMPI                 { value 92; }
      enum x213                          { value 93; }
      enum adsl                          { value 94; }
      enum radsl                         { value 95; }
      enum sdsl                          { value 96; }
      enum vdsl                          { value 97; }
      enum iso88025CRFPInt               { value 98; }
      enum myrinet                       { value 99; }
      enum voiceEM                       { value 100; }
      enum voiceFXO                      { value 101; }
      enum voiceFXS                      { value 102; }
      enum voiceEncap                    { value 103; }
      enum voiceOverIp                   { value 104; }
      enum atmDxi                        { value 105; }
      enum atmFuni                       { value 106; }
      enum atmIma                        { value 107; }
      enum pppMultilinkBundle            { value 108; }
      enum ipOverCdlc                    { value 109; }
      enum ipOverClaw                    { value 110; }
      enum stackToStack                  { value 111; }
      enum virtualIpAddress              { value 112; }
      enum mpc                           { value 113; }
      enum ipOverAtm                     { value 114; }
      enum iso88025Fiber                 { value 115; }
      enum tdlc                          { value 116; }
      enum gigabitEthernet               { value 117; }
      enum hdlc                          { value 118; }
      enum lapf                          { value 119; }
      enum v37                           { value 120; }
      enum x25mlp                        { value 121; }
      enum x25huntGroup                  { value 122; }
      enum transpHdlc                    { value 123; }
      enum interleave                    { value 124; }
      enum fast                          { value 125; }
      enum ip                            { value 126; }
      enum docsCableMaclayer             { value 127; }
      enum docsCableDownstream           { value 128; }
      enum docsCableUpstream             { value 129; }
      enum a12MppSwitch                  { value 130; }
      enum tunnel                        { value 131; }
      enum coffee                        { value 132; }
      enum ces                           { value 133; }
      enum atmSubInterface               { value 134; }
      enum l2vlan                        { value 135; }
      enum l3ipvlan                      { value 136; }
      enum l3ipxvlan                     { value 137; }
      enum digitalPowerline              { value 138; }
      enum mediaMailOverIp               { value 139; }
      enum dtm                           { value 140; }
      enum dcn                           { value 141; }
      enum ipForward                     { value 142; }
      enum msdsl                         { value 143; }
      enum ieee1394                      { value 144; }
      enum if-gsn                        { value 145; }
      enum dvbRccMacLayer                { value 146; }
      enum dvbRccDownstream              { value 147; }
      enum dvbRccUpstream                { value 148; }
      enum atmVirtual                    { value 149; }
      enum mplsTunnel                    { value 150; }
      enum srp                           { value 151; }
      enum voiceOverAtm                  { value 152; }
      enum voiceOverFrameRelay           { value 153; }
      enum idsl                          { value 154; }
      enum compositeLink                 { value 155; }
      enum ss7SigLink                    { value 156; }
      enum propWirelessP2P               { value 157; }
      enum frForward                     { value 158; }
      enum rfc1483                       { value 159; }
      enum usb                           { value 160; }
      enum ieee8023adLag                 { value 161; }
      enum bgppolicyaccounting           { value 162; }
      enum frf16MfrBundle                { value 163; }
      enum h323Gatekeeper                { value 164; }
      enum h323Proxy                     { value 165; }
      enum mpls                          { value 166; }
      enum mfSigLink                     { value 167; }
      enum hdsl2                         { value 168; }
      enum shdsl                         { value 169; }
      enum ds1FDL                        { value 170; }
      enum pos                           { value 171; }
      enum dvbAsiIn                      { value 172; }
      enum dvbAsiOut                     { value 173; }
      enum plc                           { value 174; }
      enum nfas                          { value 175; }
      enum tr008                         { value 176; }
      enum gr303RDT                      { value 177; }
      enum gr303IDT                      { value 178; }
      enum isup                          { value 179; }
      enum propDocsWirelessMaclayer      { value 180; }
      enum propDocsWirelessDownstream    { value 181; }
      enum propDocsWirelessUpstream      { value 182; }
      enum hiperlan2                     { value 183; }
      enum propBWAp2Mp                   { value 184; }
      enum sonetOverheadChannel          { value 185; }
      enum digitalWrapperOverheadChannel { value 186; }
      enum aal2                          { value 187; }
      enum radioMAC                      { value 188; }
      enum atmRadio                      { value 189; }
      enum imt                           { value 190; }
      enum mvl                           { value 191; }
      enum reachDSL                      { value 192; }
      enum frDlciEndPt                   { value 193; }
      enum atmVciEndPt                   { value 194; }
      enum opticalChannel                { value 195; }
      enum opticalTransport              { value 196; }
      enum propAtm                       { value 197; }
      enum voiceOverCable                { value 198; }
      enum infiniband                    { value 199; }
      enum teLink                        { value 200; }
      enum q2931                         { value 201; }
      enum virtualTg                     { value 202; }
      enum sipTg                         { value 203; }
      enum sipSig                        { value 204; }
      enum docsCableUpstreamChannel      { value 205; }
      enum econet                        { value 206; }
      enum pon155                        { value 207; }
      enum pon622                        { value 208; }
      enum bridge                        { value 209; }
      enum linegroup                     { value 210; }
      enum voiceEMFGD                    { value 211; }
      enum voiceFGDEANA                  { value 212; }
      enum voiceDID                      { value 213; }
      enum mpegTransport                 { value 214; }
      enum sixToFour                     { value 215; }
      enum gtp                           { value 216; }
      enum pdnEtherLoop1                 { value 217; }
      enum pdnEtherLoop2                 { value 218; }
      enum opticalChannelGroup           { value 219; }
      enum homepna                       { value 220; }
      enum gfp                           { value 221; }
      enum ciscoISLvlan                  { value 222; }
      enum actelisMetaLOOP               { value 223; }
      enum fcipLink                      { value 224; }
      enum rpr                           { value 225; }
      enum qam                           { value 226; }
      enum lmp                           { value 227; }
      enum cblVectaStar                  { value 228; }
      enum docsCableMCmtsDownstream      { value 229; }
      enum adsl2                         { value 230; }
      enum macSecControlledIF            { value 231; }
      enum macSecUncontrolledIF          { value 232; }
      enum aviciOpticalEther             { value 233; }
      enum atmbond                       { value 234; }
      enum voiceFGDOS                    { value 235; }
      enum mocaVersion1                  { value 236; }
      enum ieee80216WMAN                 { value 237; }
      enum adsl2plus                     { value 238; }
      enum dvbRcsMacLayer                { value 239; }
      enum dvbTdm                        { value 240; }
      enum dvbRcsTdma                    { value 241; }
      enum x86Laps                       { value 242; }
      enum wwanPP                        { value 243; }
      enum wwanPP2                       { value 244; }
      enum voiceEBS                      { value 245; }
      enum ifPwType                      { value 246; }
      enum ilan                          { value 247; }
      enum pip                           { value 248; }
      enum aluELP                        { value 249; }
      enum gpon                          { value 250; }
      enum vdsl2                         { value 251; }
      enum capwapDot11Profile            { value 252; }
      enum capwapDot11Bss                { value 253; }
      enum capwapWtpVirtualRadio         { value 254; }
    }
    description     
     "This data type is used as the syntax of the ifType
      object in the (updated) definition of MIB-II's
      ifTable.
      
      The definition of this textual convention with the
      addition of newly assigned values is published
      periodically by the IANA, in either the Assigned
      Numbers RFC, or some derivative of it specific to
      Internet Network Management number assignments.  (The
      latest arrangements can be obtained by contacting the
      IANA.)
      
      Requests for new values should be made to IANA via
      email (iana&iana.org).
      
      The relationship between the assignment of ifType
      values and of OIDs to particular media-specific MIBs
      is solely the purview of IANA and is subject to change
      without notice.  Quite often, a media-specific MIB's
      OID-subtree assignment within MIB-II's 'transmission'
      subtree will be the same as its ifType value.
      However, in some circumstances this will not be the
      case, and implementors must not pre-assume any
      specific relationship between ifType values and
      transmission subtree OIDs.";
  }

  typedef IANAtunnelType {
    type enumeration {
      enum other       { value 1; }
      enum direct      { value 2; }
      enum gre         { value 3; }
      enum minimal     { value 4; }
      enum l2tp        { value 5; }
      enum pptp        { value 6; }
      enum l2f         { value 7; }
      enum udp         { value 8; }
      enum atmp        { value 9; }
      enum msdp        { value 10; }
      enum sixToFour   { value 11; }
      enum sixOverFour { value 12; }
      enum isatap      { value 13; }
      enum teredo      { value 14; }
      enum ipHttps     { value 15; }
    }
    description     
     "The encapsulation method used by a tunnel. The value
      direct indicates that a packet is encapsulated
      directly within a normal IP header, with no
      intermediate header, and unicast to the remote tunnel
      endpoint (e.g., an RFC 2003 IP-in-IP tunnel, or an RFC
      1933 IPv6-in-IPv4 tunnel). The value minimal indicates
      that a Minimal Forwarding Header (RFC 2004) is
      inserted between the outer header and the payload
      packet. The value UDP indicates that the payload
      packet is encapsulated within a normal UDP packet
      (e.g., RFC 1234).
      
      The values sixToFour, sixOverFour, and isatap
      indicates that an IPv6 packet is encapsulated directly
      within an IPv4 header, with no intermediate header,
      and unicast to the destination determined by the 6to4,
      6over4, or ISATAP protocol.
      
      The remaining protocol-specific values indicate that a
      header of the protocol of that name is inserted
      between the outer header and the payload header.
      
      The assignment policy for IANAtunnelType values is
      identical to the policy for assigning IANAifType
      values.";
  }

} /* end of module IANAifType-MIB */
